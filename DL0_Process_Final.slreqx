# DL0_Process_Final

## #34: Req - Space (Functional)
Give me the answer in 15 minutes with 75% accuracy.

### #35: Func - Space (Functional)

## #36: Req - Travel on Ground (Functional)

### #37: Func - Travel on Ground (Functional)

## #38: Req - Lift (Functional)

### #39: Func - Lift (Functional)

## #40: Req - Pitch attitude (Functional)

### #41: Func - Pitch attitude (Functional)

## #42: Req - Pitching (Functional)

### #43: Func - Pitching Moment (Functional)

## #44: Req - Yawing (Functional)

### #45: Func - Yawing Moment (Functional)

## #46: Req - Source of Energy (Functional)

### #47: Func - Provide Energy (Functional)

## #48: Req - Source of Propulsion (Functional)

### #49: Func - Source of Propulsion (Functional)

## #50: Req - Takeoff (Functional)

### #52: Func - Takeoff (Functional)

## #51: Req - Landing (Functional)

### #53: Func - Landing (Functional)

## #54: Req - Fuel Tank Volume Check (Functional)

### #55: Func - Fuel Tank Volume Check (Functional)
