# DL0_Stakeholder_Final

## #1: Req - Carry Out a Mission Segment (Functional)
Aircraft shall fly a mission safely, efficiently, and effectively

### #2: Func - Airport (Functional)
Aircraft shall be idle at the airport

### #39: Func - Taxi (Functional)
Aircraft shall taxi to the runway

### #40: Func - Takeoff (Functional)
Aircraft shall takeoff

### #41: Func - Climb to Cruise (Functional)
Aircraft shall climb to cruise altitude

### #42: F - Cruise (Functional)
Aircraft shall cruise at M0.77 & Range = 1510 nautical miles

### #43: F - Descend (Functional)
Aircraft shall descend

### #44: F - Alternate Airport (Functional)
Aircraft shall fly to an alternate airport if needed.

### #45: F - Loiter (Functional)
Aircraft shall loiter

### #46: F - Land (Functional)
Aircraft shall land

### #51: F - Extra Fuel (Functional)
Aircraft shall have extra fuel for long range international flights

## #49: Req - Carry Passengers and Cargo (Functional)
