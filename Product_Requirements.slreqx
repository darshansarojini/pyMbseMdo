# Product_Requirements

## #2: Product_R (Informational)
Aircraft Wing Should Maintain Airfoil Shape(MAS)

## #4: Product_F (Functional)
Maintain the rigidity of the structure

### #5: Structural (Functional)
calculate the deflection on the airfoil given various loads that are acting on the structure

### #6: Aerodynamic (Functional)
minimize the drag on the airfoil while setting an upper threshold for the lift

## #7: Product_L (Functional)
logical solutions to the problem

### #8: Wingbox (Informational)
Wingbox Structure

### #9: Truss (Functional)
Truss Structure

## #10: Product_P (Functional)
Physical Diagrams
