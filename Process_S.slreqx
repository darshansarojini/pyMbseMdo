# Process_S

## #1: Process_S_R (Functional)
Compute the deflection of the airfoil

## #2: Process_S_F (Functional)
Deflection <1mm

## #3: Process_S_L (Functional)
3 logical options

### #5: Beam (Functional)

### #6: Shell (Functional)

### #7: CAD_Model (Functional)

### #8: Process_A_F (Functional)
Lift<1000

## #4: Process_S_P (Functional)
Physical Diagram
