# DL0_Stakeholder

## #1: Req - Carry Out a Mission Segment (Functional)
The Aircraft shall carry out a mission segment from Idle, taxi to loitering and landing.

## #2: Req - Aircraft shall carry passengers and cargo (Functional)
Aircraft shall carry passengers and cargo not exceeding the maximum weight
