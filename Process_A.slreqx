# Process_A

## #1: Process_A_R (Functional)
Minimize the drag on the airfoil

## #2: Process_A_F (Functional)
Lift<1000

## #3: Process_A_L (Functional)
Logical Options

### #6: Database (Functional)

### #7: X-Foil (Functional)

### #8: Surrogate_Model (Functional)

## #4: Process_A_P (Functional)
