# DL0_Product_Final

## #1: Req - Space (Functional)
Aircraft shall have space for passengers and cargo

### #2: Func - Space (Functional)
Aircraft's space should be enough for the number of passengers and the weight of the cargo

## #3: Req - Travel on Ground (Functional)
Aircraft shall have a means to travel on the ground

### #4: Func - Travel on Ground (Functional)
Aircraft travels on the ground

## #5: Req - Lift (Functional)
Aircraft shall product lift

### #9: Func - Lift (Functional)

## #6: Req - Nose up (Functional)
Aircraft shall point its nose up

### #7: Derived Req - Pitch attitude (Functional)
Aircraft shall change its pitch attitude

#### #8: Func - Pitch attitude (Functional)
Generate Pitch Control

## #10: Req - Stablility (Functional)
Aircraft shall be stable in flight

### #11: Derived Req - Pitching (Functional)
Aircraft shall be stable during pitching

#### #12: Func - Pitching Moment (Functional)
Generate restorative pitching moment

### #13: Derived Req - Yawing (Functional)
Aircraft shall be stable during yawing

#### #14: Func - Yawing Moment (Functional)
Generate restorative yawing moment

## #15: Req - Source of Propulsion (Functional)
Aircraft shall have a source of propulsion

### #17: Func - Propulsive Power (Functional)
Aircraft will produce thrust

## #16: Req - Source of Energy (Functional)
Aircraft shall utilize a source of energy to power it during flight

### #18: Func - Provide Energy (Functional)
Aircraft provides energy

## #19: Req - Takeoff (Functional)
Aircraft shall takeoff at the designated airport

### #20: Func - Takeoff (Functional)
Aircraft shall move from ground to air

## #21: Req - Landing (Functional)
Aircraft shall land at the designated airport

### #22: Func - Landing (Functional)
Aircraft shall move from air to ground

## #23: Req - Fuel Tank Volume Check (Functional)
The Fuel Tank Volume shall be checked while being idle at the airport

### #24: Func - Fuel Tank Volume Check (Functional)
Aircraft shall have the needed fuel for the mission
